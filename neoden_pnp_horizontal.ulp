#usage  "<b>PNP component script for NEO-DEN 4 machines</b>\n"
        "<p>"
        "Generates files for smds on the top layer"
        "units are in mm"
        "</p>"
        "<author>Author: SoC</author>"

// THIS PROGRAM IS PROVIDED AS IS AND WITHOUT WARRANTY OF ANY KIND, EXPRESSED OR IMPLIED, MAY RESULT IN DEATH

real detectX = 350.0; //This is the number on the machine
real detectXOffset = -5.15; //This is the diffrence between detectX and 0,0
real xOffset = detectX + detectXOffset;

real detectY = 350.0; //This is the number on the machine
real detectYOffset = 0.56; //This is the diffrence between detectY and 0,0
real yOffset = detectY + detectYOffset;

if (board) board(B) {

    // Get filename
    string fileName = dlgFileSave("Name this here file", filesetext(B.name, ".csv"), "*.csv");
    if (fileName == "") exit(0);

    output(fileName) {

        printf("#SMD,Feeder ID,Nozzle,Name,Value,Footprint,X,Y,Rotation,Skip,\n");

        B.elements(E) {

            int isSmd,
                xmax =-2147483648,
                xmin = 2147483647,
                ymax = xmax,
                ymin = xmin;
            real angle = 0.0;

            isSmd = 0;

            E.package.contacts(C) {
                if (C.smd && C.smd.layer == 1) {
                    isSmd = 1;

                    if (C.x > xmax) xmax = C.x;
                    if (C.y > ymax) ymax = C.y;
                    if (C.x < xmin) xmin = C.x;
                    if (C.y < ymin) ymin = C.y;

                    angle = (E.angle > 180.0) ? (E.angle - 360.0) : E.angle;
                }
            }

            if (isSmd){

                printf("comp,");
                printf("1,"); //Feeder ID - needs to be verified
                printf("1,"); //Nozzle - needs to be verified
                printf("%s,", E.name);
                printf("%s,", E.value);
                printf("%s,", E.package.name);
                printf("%4.2f,", yOffset - u2mm((ymin + ymax)/2));
                printf("%4.2f,", xOffset + u2mm((xmin + xmax)/2));
                printf("%3.2f,", angle); //Angle - double check this
                printf("No,"); //Skip
                printf("\n");

            }
        }
    }
} else {
    dlgMessageBox("\n    Open up a board view, then start this ulp. Silly.    \n");
    exit (0);
}
